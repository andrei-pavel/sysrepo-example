module model {
  yang-version 1.1;
  namespace "urn:ietf:params:xml:ns:yang:model";
  prefix model;

  revision 2020-01-09;

  container config {
    list le_list {
      key "name";
      leaf name {
        type string;
        mandatory true;
      }

      container contained {
        leaf data {
            type string;
        }
        leaf floating {
          type decimal64 {
            fraction-digits 18;
            range "0 .. 1";
          }
        }
      }
      list le_nested_list {
        key "a b c d";
        leaf a {
          type int32;
        }
        leaf b {
          type int32;
        }
        leaf c {
          type int32;
        }
        leaf d {
          type int32;
        }
      }
      leaf-list le_leaf_list {
        type string;
      }
    }
    leaf child {
        type int32;
    }
  }
}
